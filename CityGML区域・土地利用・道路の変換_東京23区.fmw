FME workspace CityGML区域・土地利用・道路の変換_東京23区.fmw

Parameters:
- CITYMODEL_ROOT_DIR = C:\Users\takas\PSS Dropbox\All_Project\20200001_mri_digitaltwin\03_受領データ整理\東京23区+南大沢\20210129_国際航業納品\13100_東京23区   # 3D都市モデルルートフォルダー
- DISTRICT_FOLDER_NAME = 13100_tokyo   # 地域フォルダー名 {コード}_{地域名（英）}
- STANDARD_CODELISTS_DIR = $(FME_MF_DIR)resources\標準製品仕様_コードリスト0118_0120修正適用済み\標準製品仕様_コードリスト   # 標準コードリスト（XML）フォルダー
- DEST_ROOT_DIR = $(FME_MF_DIR)20210213_八王子土地利用等変換結果   # 変換結果出力先ルートフォルダー
- DestDataset_OGCGEOPACKAGE = $(DEST_ROOT_DIR)/gpkg/$(DISTRICT_FOLDER_NAME).gpkg   # GeoPackage File
- DestDataset_GEOJSON = $(DEST_ROOT_DIR)/geojson   # Destination GeoJSON Folder

Readers:
- PATH_1: PATH from $(CITYMODEL_ROOT_DIR)

Writers:
- GEOJSON_1: GEOJSON to $(DestDataset_GEOJSON)
- OGCGEOPACKAGE_1: OGCGEOPACKAGE to $(DestDataset_OGCGEOPACKAGE)

PATH (reader PATH_1)
    attributes: path_unix buffer, path_windows buffer, path_rootname buffer, path_filename buffer, path_extension buffer, path_filesize buffer, path_ownername buffer, path_readonly buffer, path_modified_date date, path_created_date date, path_accessed_date date, path_directory_unix buffer, path_directory_windows buffer, path_type char(10)
    -> TestFilter
TestFilter
    DEFAULT_VALUE = <UNFILTERED>
    TEST_LIST = "BOOL_OP,OR,COMPOSITE_TEST,""""""1"""""",TEST_CLAUSE,TEST @Value(path_rootname) = tran",tran,"BOOL_OP,OR,COMPOSITE_TEST,""""""1"""""",TEST_CLAUSE,TEST @Value(path_rootname) = luse",luse,"BOOL_OP,OR,COMPOSITE_TEST,""""""1"""""",TEST_CLAUSE,TEST @Value(path_rootname) = urf",urf,"BOOL_OP,OR,COMPOSITE_TEST,""""""1"""""",TEST_CLAUSE,TEST @Value(path_rootname) = codelists",codelists
    tran -> FilePathExtractor
    luse -> FilePathExtractor_2
    urf -> FilePathExtractor_3
    codelists -> AttributeManager
FilePathExtractor
    DIRECTORY = @Value(path_unix)
    -> FeatureReader_tran [INITIATOR]
FeatureReader_tran
    ATTRS_TO_EXPOSE = gml_id fme_feature_type
    ATTR_ACCUM_MODE = Only Use Result
    CITYGML_ADD_NAMESPACE_PREFIX_TO_FEATURE_TYPES = No
    CITYGML_GENERIC_ATTRS_AS_FEATURES = No
    CITYGML_GENERIC_ATTRS_AS_SCHEMA_ATTRS = Yes
    CITYGML_LODS_TO_READ = 1 0
    CITYGML_MATERIAL_FEATURES = No
    CITYGML_MAX_ATTRIBUTES_PER_NESTED_ATTRIBUTE = 400
    CITYGML_ONLY_FEATURE_TYPES_IN_DATASET = YES
    CITYGML_SKIP_SCHEMA_LOCATION_IN_DATASET = No
    CITYGML_SRS_AXIS_ORDER = 2,1,3
    CITYGML_TEXTURE_COORDINATES_ORDER_FIX = No
    CITYGML_USE_CITYGML_SCHEMA_FILES = Yes
    CITYGML_USE_SEARCH_ENVELOPE = NO
    CITYGML_USE_XLINK_HREF_GEOMETRY_TRAITS = Yes
    CITYGML_VALIDATE_DATASET = no
    COMBINE_GEOM = Use Result
    DATASET = @Value(path_unix)
    FORMAT = CITYGML
    INTERACT = <No Spatial Filter>
    OUTPUT_FEATURES_DISPLAY = Schema and Data Features
    <OTHER> -> Tester_3
    <REJECTED> -> Junction_7
Tester_3
    BOOL_OP = OR
    COMPOSITE_TEST = 1
    TEST_CLAUSE = TEST @Value(fme_feature_type) = Road
    TEST_MODE = TEST
    PASSED -> GeometryPartExtractor
GeometryPartExtractor
    GQUERY:
      for $geom in //geometry
      where $geom/@fme_geometry_type = 'IFMEPolygon'
      return number($geom/@fme_id)
    EXTRACTED -> 2DForcer_2
2DForcer_2
    2D -> road (writer OGCGEOPACKAGE_1)
    2D -> AttributeCreator_5
AttributeCreator_5
    ATTR_TABLE = SET_TO _dataset_name = road
    -> road (writer GEOJSON_1)
road (writer GEOJSON_1)
    attributes: gml_id string
road (writer OGCGEOPACKAGE_1)
    attributes: gml_id text
Junction_7
FilePathExtractor_2
    DIRECTORY = @Value(path_unix)
    -> FeatureReader_luse [INITIATOR]
FeatureReader_luse
    ATTRIBUTES = LandUse,"LandUse.id,areaInHa,areaInHa.uom,areaInSquareMeter,areaInSquareMeter.uom,city,city.codeSpace,genericAttributeSet{}.measureAttribute.name,genericAttributeSet{}.measureAttribute.value,genericAttributeSet{}.measureAttribute.value.uom,genericAttributeSet{}.name,genericAttributeSet{}.stringAttribute{}.name,genericAttributeSet{}.stringAttribute{}.value,lod1MultiSurface.MultiSurface.surfaceMember.Polygon.exterior.LinearRing.posList,lod1MultiSurface.MultiSurface.surfaceMember.Polygon.interior.LinearRing.posList,lod1MultiSurface.MultiSurface.surfaceMember.Polygon.interior{}.LinearRing.posList,lod1MultiSurface.MultiSurface.surfaceMember{}.Polygon.exterior.LinearRing.posList,lod1MultiSurface.MultiSurface.surfaceMember{}.Polygon.interior.LinearRing.posList,lod1MultiSurface.MultiSurface.surfaceMember{}.Polygon.interior{}.LinearRing.posList,prefecture,prefecture.codeSpace,surveyYear,xml_fragment,xml_id,xml_matched_element,xml_parent_child_pos,xml_parent_id"
    ATTR_ACCUM_MODE = Only Use Result
    COMBINE_GEOM = Use Result
    DATASET = @Value(path_unix)
    FORMAT = XML
    INTERACT = <No Spatial Filter>
    OUTPUT_FEATURES_DISPLAY = Schema and Data Features
    XML_CONTINUE_ON_GEOM_ERROR = no
    XML_FILE_TYPE = Feature Paths
    XML_USE_SEARCH_ENVELOPE = NO
    XML_VALIDATE_DATASET = no
    XML_VALIDATE_XFMAP = no
    XML_XFMAP_FEATURE_PATHS = CityModel/cityObjectMember/LandUse
    XML_XFMAP_FEATURE_PATHS_STRUCTURE:
      <structure
      separator="."
      open-list-brace="{"
      close-list-brace="}"
      map-empty-elements="yes"
      matched-prefix="attributes"
      matched-attributes="yes"
      matched-ancestor-attributes=""
      cardinality="
          */genericAttributeSet{}/stringAttribute{}/+
          */genericAttributeSet{}/+
          */stringAttribute{}/+
          +{?}
      "
      except="lod0MultiSurface"
      structure-prefix=""
      child-position-attribute=""
      attribute-identifier=""/>

      <!--
      The options here allows customization of the attributes and attribute lists of the matched XML subtree
      that will be added to FME Features.

      Here are the following options that can be specified:

      1. separator
      This value of this option is used as the separator in the naming of the attributes of the children of the matched elements.

      Default value: .
      Possible values: any string

      2. open-list-brace
      Specifies the open list index delimiter brace for the flattened attributes.

      Default value: {
      Possible values: any string

      3. close-list-brace
      Specifies the close list index delimiter brace for the flattened attributes.

      Default value: }
      Possible values: any string

      4. map-empty-elements
      If set to yes, then any empty elements will be added as attributes with empty values onto the features.
      Otherwise, the attributes will not be added onto the features.

      Default value if not specified: yes
      Possible values: yes|no

      Default value:
      Possible values: any string

      5. matched-prefix
      This option controls whether FME feature attributes produced will be prefixed with matched element's name.
      If the value is 'yes', then both the matched element's attributes and all its children are prefixed
      If the value is 'no', then none of the feature attributes are prefixed with matched element's name
      If the value is 'children', then only the children of the matched element are prefixed
      If the value is 'attributes', then only the attributes of the matched element are prefixed

      Default value if not specified: yes
      Possible values: yes|no|children|attributes

      6. matched-attributes
      If this option is set to 'yes' then the attributes of the matched element are mapped as FME feature attributes.
      Otherwise, the attributes of the matched element are ignored.

      matched-prefix option can also be set to 'attributes' or 'yes' to allow the attributes to be prefixed with
      the name of the matched element.

      Default value if not specified: yes
      Possible values: yes|no

      7. matched-ancestor-attributes
      The option controls whether XML attributes from ancestor of the matched element should be included as FME feature attributes.

      The valid values for this option are:
      - 'parent' or '1'         : XML attributes of the parent of the matched element are added
      - 'grandparent' or '2'    : XML attributes of the grandparent of the matched element are added
      - 'root' or '-1'          : XML attributes of the root of the document are added
      - any non-negative number : XML attributes of the ancestor by going up x levels from the matched element are added.
                                  0 is the matched element.

      To include more than one ancestor, multiple values can be separated by a space.
      For example: To get the attributes from root, parent and grand parent, we can specify
      matched-ancestor-attributes="parent grandparent root"

      Default value:
      Possible values: parent|grandparent|root

      8. cardinality
      This option can be specified as a space separated list of cardinality directives.

      Default value: +{?} (Treat child elements as a list if there are more than one with the same name)
      Possible values: Refer to the documentation of XFMap section in XML Reader documentation

      9. structure-prefix
      This option can be set to non-empty string that serves as a prefix to every attribute that is generated for a matched element.

      Default value:
      Possible values: any string

      10. except
      The except attribute accepts the same types of expressions as the match or except attribute of a mapping rule.
      For example, the expression except=”parent/child{2}” could be used to exclude the second <child> element
      contained in a <parent> element from the output of the structure subrule.

      Default value:
      Possible values: any path expression

      11. child-position-attribute
      When this option is set to non-empty string, each child element will generate an additional feature attribute
      whose value will be the position of the child element witihin its parent.

      Default value:
      Possible values: any string

      12. attribute-identifier (Any string)
      XML attributes can be differentiated from leaf elements. By setting this option to non-empty string, XML reader
      will append a prefix to the attributes in the leaf elements.

      All the options have more elaborated examples and descriptions in the XML reader documentation.
      -->
    LandUse -> GeometryReplacer
    <REJECTED> -> Junction_3
GeometryReplacer
    KIND_LONG = GML
    REMOVE_ATTRIBUTE = Yes
    SOURCE = @Value(xml_fragment)
    SRS_AXIS_ORDER_DISPLAY = 2,1,3
    -> FeatureMerger_5 [REQUESTOR]
Junction_3
FilePathExtractor_3
    DIRECTORY = @Value(path_unix)
    -> FeatureReader_urf [INITIATOR]
FeatureReader_urf
    ATTRS_TO_EXPOSE = gml_id urf_class urf_class_value urf_class_codeSpace urf_nominalArea urf_prefecture urf_prefecture_value urf_prefecture_codeSpace urf_city urf_city_value urf_city_codeSpace fme_feature_type
    ATTR_ACCUM_MODE = Only Use Result
    CITYGML_ADD_NAMESPACE_PREFIX_TO_FEATURE_TYPES = No
    CITYGML_GENERIC_ATTRS_AS_FEATURES = No
    CITYGML_GENERIC_ATTRS_AS_SCHEMA_ATTRS = Yes
    CITYGML_LODS_TO_READ = 1 0
    CITYGML_MATERIAL_FEATURES = No
    CITYGML_MAX_ATTRIBUTES_PER_NESTED_ATTRIBUTE = 400
    CITYGML_ONLY_FEATURE_TYPES_IN_DATASET = YES
    CITYGML_SKIP_SCHEMA_LOCATION_IN_DATASET = No
    CITYGML_SRS_AXIS_ORDER = 2,1,3
    CITYGML_TEXTURE_COORDINATES_ORDER_FIX = No
    CITYGML_USE_CITYGML_SCHEMA_FILES = Yes
    CITYGML_USE_SEARCH_ENVELOPE = NO
    CITYGML_USE_XLINK_HREF_GEOMETRY_TRAITS = Yes
    CITYGML_VALIDATE_DATASET = no
    COMBINE_GEOM = Use Result
    DATASET = @Value(path_unix)
    FORMAT = CITYGML
    INTERACT = <No Spatial Filter>
    OUTPUT_FEATURES_DISPLAY = Schema and Data Features
    <OTHER> -> Tester
    <REJECTED> -> Junction
Tester
    BOOL_OP = OR
    COMPOSITE_TEST = 1
    TEST_CLAUSE = TEST @Value(fme_feature_type) IN UrbanPlan,AreaClassification,DistrictsAndZones
    TEST_MODE = TEST
    PASSED -> FeatureMerger_4 [REQUESTOR]
Junction
AttributeManager
    ATTR_TABLE:
      RENAME_SET_VALUE path_unix > _codelists_dir
      REMOVE path_windows
      REMOVE path_rootname
      REMOVE path_filename
      REMOVE path_extension
      REMOVE path_filesize
      REMOVE path_ownername
      REMOVE path_readonly
      REMOVE path_modified_date
      REMOVE path_created_date
      REMOVE path_accessed_date
      REMOVE path_directory_unix
      REMOVE path_directory_windows
      REMOVE path_type
    -> MLIT.CityGMLCodeListsReader [Initiator]
MLIT.CityGMLCodeListsReader
    CUSTOM_CODELIST_FOLDER = @Value(_codelists_dir)
    DICTIONARY_TYPE = JSON
    STANDARD_CODELIST_FOLDER = $(STANDARD_CODELISTS_DIR)
    Dictionary -> Junction_8
Junction_8
    -> FeatureMerger_4 [SUPPLIER]
    -> FeatureMerger_5 [SUPPLIER]
FeatureMerger_5
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> AttributeExposer
Note: 表示必須属性を現わしておく
AttributeExposer
    ATTR_LIST = class,class.codeSpace,nominalArea,areaInSquareMeter,areaInHa,prefecture,prefecture.codeSpace,city,city.codeSpace,surveyYear
    -> Tester_4
Tester_4
    BOOL_OP = OR
    COMPOSITE_TEST = 1
    TEST_CLAUSE = TEST class ATTRIBUTE_HAS_A_VALUE ""
    TEST_MODE = TEST
    PASSED -> AttributeRenamer
AttributeRenamer
    ATTR_TABLE:
      RENAME_SET_DEFAULT class > class_code
      RENAME_SET_DEFAULT prefecture > prefecture_code
      RENAME_SET_DEFAULT city > city_code
    -> StringReplacer_2
StringReplacer_2
    CASE = NO
    FIND_TEXT = .+/codelists/
    NO_MATCH = _FME_NO_OP_
    REGEXP = YES
    SRC_ATTRS = city.codeSpace,class.codeSpace,prefecture.codeSpace
    -> PythonCaller_2
Note: ・コード から意味文字列への変換 / ・汎用属性の抽出 / 土地利用区分（都道府県区分） / 土地利用区分（市区町村区分）
PythonCaller_2
    NEW_ATTRIBUTES = class_value prefecture_value city_value landuse_prefecture landuse_city
    PYTHONSOURCE:
      import fme
      import fmeobjects, os, json
      class CodeValueConverter_luse(object):
          def __init__(self):
              self.dictionaries = None

          def input(self,feature):
              # 辞書名（コードリストファイル名）はLowerCaseで扱う。
              if self.dictionaries == None:
                  j = json.loads(feature.getAttribute('_codelists'))
                  self.dictionaries = {}
                  for name, entries in j.items():
                      self.dictionaries[name.lower()] = {e['key'] : e['value'] for e in entries}

              attrs = [
                  'class',
                  'prefecture',
                  'city',
              ]

              for attr in attrs:
                  d = feature.getAttribute(attr + '.codeSpace')
                  dict = self.dictionaries.get(d.lower(), None) if d else None
                  if dict:
                      code = feature.getAttribute(attr + '_code')
                      value = dict.get(code, '')
                      feature.setAttribute(attr + '_value', value)

              # 汎用属性セット
              attrNames = {
                  '土地利用区分（都道府県区分）' : 'landuse_prefecture',
                  '土地利用区分（市区町村区分）' : 'landuse_city',
              }
              attrSetNames = feature.getAttribute('genericAttributeSet{}.name')
              if attrSetNames:
                  attributes = {}
                  for i, setName in enumerate(attrSetNames):
                      attr = attrNames.get(setName, None)
                      if attr:
                          prefix = 'genericAttributeSet{%d}' % i
                          keys = feature.getAttribute(prefix + '.stringAttribute{}.name')
                          keyValue = {}
                          for j, k in enumerate(keys):
                              keyValue[k] = feature.getAttribute('%s.stringAttribute{%d}.value' % (prefix, j))
                          code = keyValue.get('code', None)
                          codeSpace = keyValue.get('codeSpace', None)
                          if code and codeSpace:
                              import os
                              dict = self.dictionaries.get(os.path.split(codeSpace)[-1].lower(), {})
                              value = dict.get(code, code) if dict else code
                              feature.setAttribute(attr, value)

              self.pyoutput(feature)

          def close(self):
              pass
    PYTHONSYMBOL = CodeValueConverter_luse
    -> AttributeManager_6
AttributeManager_6
    ATTR_TABLE:
      RENAME_SET_VALUE LandUse.id > gml_id
      RENAME_SET_VALUE class_value > class
      RENAME_SET_VALUE nominalArea > nominal_area
      RENAME_SET_VALUE areaInSquareMeter > area_m2
      RENAME_SET_VALUE areaInHa > area_ha
      RENAME_SET_VALUE prefecture_value > prefecture
      RENAME_SET_VALUE city_value > city
      RENAME_SET_VALUE surveyYear > survey_year
      REMOVE city.codeSpace
      REMOVE class.codeSpace
      REMOVE genericAttributeSet{}.name
      REMOVE genericAttributeSet{}.stringAttribute{}.name
      REMOVE genericAttributeSet{}.stringAttribute{}.value
      REMOVE prefecture.codeSpace
      REMOVE xml_id
      REMOVE xml_matched_element
      REMOVE xml_parent_child_pos
      REMOVE xml_parent_id
      REMOVE _codelists
      REMOVE class_code
      REMOVE prefecture_code
      REMOVE city_code
      REMOVE lod1MultiSurface.MultiSurface.surfaceMember.Polygon.exterior.LinearRing.posList
      REMOVE areaInHa.uom
      REMOVE areaInSquareMeter.uom
      REMOVE genericAttributeSet{}.measureAttribute.name
      REMOVE genericAttributeSet{}.measureAttribute.value
      REMOVE genericAttributeSet{}.measureAttribute.value.uom
      REMOVE lod1MultiSurface.MultiSurface.surfaceMember.Polygon.interior.LinearRing.posList
      REMOVE lod1MultiSurface.MultiSurface.surfaceMember.Polygon.interior{}.LinearRing.posList
      REMOVE lod1MultiSurface.MultiSurface.surfaceMember{}.Polygon.exterior.LinearRing.posList
      REMOVE lod1MultiSurface.MultiSurface.surfaceMember{}.Polygon.interior.LinearRing.posList
      REMOVE lod1MultiSurface.MultiSurface.surfaceMember{}.Polygon.interior{}.LinearRing.posList
    -> luse (writer OGCGEOPACKAGE_1)
    -> AttributeCreator_6
AttributeCreator_6
    ATTR_TABLE = SET_TO _dataset_name = luse
    -> luse (writer GEOJSON_1)
luse (writer GEOJSON_1)
    attributes: gml_id string, class string, landuse_prefecture string, landuse_city string, nominal_area float, area_m2 float, area_ha float, prefecture string, city string, survey_year int
luse (writer OGCGEOPACKAGE_1)
    attributes: gml_id text, class text, landuse_prefecture text, landuse_city text, nominal_area double, area_m2 double, area_ha double, prefecture text, city text, survey_year mediumint
FeatureMerger_4
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> StringReplacer
StringReplacer
    CASE = NO
    FIND_TEXT = .+/codelists/
    NO_MATCH = _FME_NO_OP_
    REGEXP = YES
    SRC_ATTRS = urf_city_codeSpace,urf_class_codeSpace,urf_prefecture_codeSpace
    -> PythonCaller
PythonCaller
    PYTHONSOURCE:
      import fme
      import fmeobjects, json
      class CodeValueConverter_urf(object):
          def __init__(self):
              self.dictionaries = None

          def input(self,feature):
              if self.dictionaries == None:
                  j = json.loads(feature.getAttribute('_codelists'))
                  self.dictionaries = {}
                  for name, entries in j.items():
                      self.dictionaries[name.lower()] = {e['key'] : e['value'] for e in entries}

              attrs = [
                  'class',
                  'prefecture',
                  'city',
              ]

              for attr in attrs:
                  d = feature.getAttribute('urf_' + attr + '_codeSpace')
                  dict = self.dictionaries.get(d.lower(), None) if d else None
                  if dict:
                      code = feature.getAttribute('urf_' + attr)
                      value = dict.get(code, '')
                      feature.setAttribute('urf_' + attr + '_value', value)

              self.pyoutput(feature)

          def close(self):
              pass
    PYTHONSYMBOL = CodeValueConverter_urf
    -> AttributeValueMapper
AttributeValueMapper
    DIRECTION = Forward (Source To Destination)
    LUT = UrbanPlan,都市計画区域,AreaClassification,区域区分,DistrictsAndZones,地域地区/用途地域
    SRC = fme_feature_type
    VAL_ATTR = typename
    -> AttributeManager_5
AttributeManager_5
    ATTR_TABLE:
      SET_TO type = @Value(fme_feature_type)
      REMOVE urf_class
      RENAME_SET_VALUE urf_class_value > class
      REMOVE urf_class_codeSpace
      RENAME_SET_VALUE urf_nominalArea > nominal_area
      REMOVE urf_prefecture
      RENAME_SET_VALUE urf_prefecture_value > prefecture
      REMOVE urf_prefecture_codeSpace
      REMOVE urf_city
      RENAME_SET_VALUE urf_city_value > city
      REMOVE urf_city_codeSpace
      REMOVE _codelists
    -> 2DForcer
2DForcer
    2D -> urf (writer OGCGEOPACKAGE_1)
    2D -> AttributeCreator_7
AttributeCreator_7
    ATTR_TABLE = SET_TO _dataset_name = urf
    -> urf (writer GEOJSON_1)
urf (writer GEOJSON_1)
    attributes: gml_id string, type string, typename string, class string, nominal_area float, prefecture string, city string
urf (writer OGCGEOPACKAGE_1)
    attributes: gml_id text, type text, typename text, class text, nominal_area double, prefecture text, city text

FME custom transformer FileExistenceChecker
Description
This transformer checks if input file paths exist and routes features accordingly.
The transformer supports UNC path, Zip files(*.zip) and wildcards. 
Details
The transformer will check if the filename selected in InputPort exists or not. 
The path can be supplied from a parameter, a network share location, by selecting a filename or using wildcards. 
Notes
Multiple filenames are not supported
Path to file must exist (no missing folders in the path)
FTP paths are not supported
Input
Filename path to check if file exists.   
Parameters
Input ports
Input File Path: Full path to the file to check for existence.  
Output Ports
Exists:Features are output through this port if the file exists.   
_path: The attribute stores the path to the file.  
DoesNotExist:Features are output through this port if the file does not exists.   
_path: This attribute stores the path to the file.

Parameters:
- Input =   # Input File Path

Input (input)
    -> ParameterFetcher
ParameterFetcher
    ATTR_LIST = FEC_FullPath {$(Input)}
    -> PythonCaller
AttributeManager
    ATTR_TABLE = REMOVE FEC_exists
    -> Exists (output)
Exists (output)
AttributeManager_2
    ATTR_TABLE = REMOVE FEC_exists
    -> DoesNotExist (output)
DoesNotExist (output)

Bookmark: Check if File Exists
PythonCaller
    NEW_ATTRIBUTES = FEC_exists
    PYTHONSOURCE:
      import fmeobjects
      import glob
      import zipfile

      def processFeature(feature):

          # Get input path attribute
          fullpath=feature.getAttribute("FEC_FullPath")

          # Check if the file exists
          if glob.glob(fullpath):
              feature.setAttribute("FEC_exists","Yes")
              # if not, try checking inside a zip file
          else:
              fullpath = fullpath.replace("\\","/")
              idx = fullpath.find(".zip")
              if idx > -1:
                  zipPath = fullpath[:idx+4]
                  pathInZip = fullpath[idx+5:]    #i.e. .zip/
                  try:
                      with zipfile.ZipFile(zipPath, 'r') as f:
                          if isinstance(f.getinfo(pathInZip),zipfile.ZipInfo):
                              feature.setAttribute("FEC_exists","Yes")
                              return
                  except (KeyError, FileNotFoundError) as e:
                      pass
                  # not found in a zipfile or in filesystem - does not exist
                  feature.setAttribute("FEC_exists","No")
    PYTHONSYMBOL = processFeature
    -> AttributeRenamer
AttributeRenamer
    ATTR_TABLE = RENAME_SET_DEFAULT FEC_FullPath > _path
    -> Tester
Tester
    BOOL_OP = OR
    COMPOSITE_TEST = 1
    TEST_CLAUSE = TEST @Value(FEC_exists) = Yes
    TEST_MODE = TEST
    PASSED -> AttributeManager
    FAILED -> AttributeManager_2

FME custom transformer MLIT.CityGMLCodeListsReader

Parameters:
- STANDARD_CODELIST_FOLDER = C:\Users\takas\PSS Dropbox\All_Project\20200001_mri_digitaltwin\20210205_CityGML都市モデル変換\全国展開\resources\標準製品仕様_コードリスト   # 標準コードリスト（XML）フォルダー
- CUSTOM_CODELIST_FOLDER = C:\Users\takas\PSS Dropbox\All_Project\20200001_mri_digitaltwin\20210205_CityGML都市モデル変換\全国展開\東京23区\20201209_CityGML東京23区データ\LOD2整備範囲外\13100\codelists   # カスタムコードリスト（XML）フォルダー
- DICTIONARY_TYPE = XML   # 統合コードリストの形式

Initiator (input)
    -> ParameterFetcher
ParameterFetcher
    ATTR_LIST = _codelists_dir $(CUSTOM_CODELIST_FOLDER)
    -> AttributeKeeper
    -> AttributeKeeper_2
AttributeKeeper
    CREATE_BULK_MODE_FEATURES = NO
    KEEP_ATTRS = _codelists_dir
    -> FileExistenceChecker
FileExistenceChecker
    Input = @Value(_codelists_dir)
    Exists -> FeatureReader [INITIATOR]
Note: カスタムコードリスト / ファイルパス取得 [PATH]
FeatureReader
    ATTRIBUTES = PATH,"path_unix,path_windows,path_rootname,path_filename,path_extension,path_filesize,path_ownername,path_readonly,path_modified_date,path_created_date,path_accessed_date,path_directory_unix,path_directory_windows,path_type,fme_geometry{0}"
    ATTR_ACCUM_MODE = Only Use Result
    COMBINE_GEOM = Use Result
    DATASET = @Value(_codelists_dir)
    FORMAT = PATH
    OUTPUT_FEATURES_DISPLAY = Schema and Data Features
    PATH_GLOB_PATTERN = *.{xml,zip}
    PATH_NO_EMPTY_PROPERTIES = YES
    PATH_RECURSE_DIRECTORIES = NO
    PATH_RETRIEVE_FILE_PROPERTIES = NO
    PATH_TYPE = FILE
    PATH -> Tester
Tester
    BOOL_OP = OR
    COMPOSITE_TEST = 1
    TEST_CLAUSE = TEST @Value(path_extension) = zip
    TEST_MODE = TEST
    PASSED -> FeatureReader_4 [INITIATOR]
    FAILED -> StringCaseChanger
FeatureReader_4
    ATTRIBUTES = PATH,"path_unix,path_windows,path_rootname,path_filename,path_extension,path_filesize,path_ownername,path_readonly,path_modified_date,path_created_date,path_accessed_date,path_directory_unix,path_directory_windows,path_type,fme_geometry{0}"
    ATTR_ACCUM_MODE = Only Use Result
    COMBINE_GEOM = Use Result
    DATASET = @Value(path_unix)
    FORMAT = PATH
    OUTPUT_FEATURES_DISPLAY = Schema and Data Features
    PATH_GLOB_PATTERN = *.xml
    PATH_NO_EMPTY_PROPERTIES = YES
    PATH_RECURSE_DIRECTORIES = NO
    PATH_RETRIEVE_FILE_PROPERTIES = NO
    PATH_TYPE = FILE
    PATH -> StringCaseChanger
AttributeKeeper_2
    CREATE_BULK_MODE_FEATURES = NO
    -> FeatureReader_2 [INITIATOR]
Note: 標準コードリスト / パス取得 [PATH]
Note: データ内のcodeSpace属性に記述されているコードリストファイル名と実際のファイル名の間で大文字小文字の相違による不一致があったため、辞書の識別子としては小文字にそろえて扱うこととした。
FeatureReader_2
    ATTRIBUTES = PATH,"path_unix,path_windows,path_rootname,path_filename,path_extension,path_filesize,path_ownername,path_readonly,path_modified_date,path_created_date,path_accessed_date,path_directory_unix,path_directory_windows,path_type,fme_geometry{0}"
    ATTR_ACCUM_MODE = Only Use Result
    COMBINE_GEOM = Use Result
    DATASET = $(STANDARD_CODELIST_FOLDER)
    FORMAT = PATH
    OUTPUT_FEATURES_DISPLAY = Schema and Data Features
    PATH_GLOB_PATTERN = *.xml
    PATH_NO_EMPTY_PROPERTIES = YES
    PATH_RECURSE_DIRECTORIES = NO
    PATH_RETRIEVE_FILE_PROPERTIES = NO
    PATH_TYPE = FILE
    PATH -> StringCaseChanger_2
Note: 同名の場合はカスタム / コードリストを優先して統合
FeatureMerger
    ATTR_ACCUM_MODE = Merge Supplier
    ATTR_CONFLICT_RES = Use Requestor
    IGNORE_NULLS = No
    JOIN_KEYS = @Value(path_filename) @Value(path_filename) AUTO
    MERGE_TYPE = Attributes Only
    PROCESS_DUPS = NO
    REJECT_NULL_MISSING_KEYS = No
    SUPPLIERS_FIRST = No
    MERGED -> AttributeManager
    UNMERGED_REQUESTOR -> AttributeManager
    UNUSED_SUPPLIER -> AttributeManager
AttributeManager
    ATTR_TABLE:
      RENAME_SET_VALUE path_filename > _codelist_name
      REMOVE path_windows
      REMOVE path_rootname
      REMOVE path_extension
      REMOVE path_filesize
      REMOVE path_ownername
      REMOVE path_readonly
      REMOVE path_modified_date
      REMOVE path_created_date
      REMOVE path_accessed_date
      REMOVE path_directory_unix
      REMOVE path_directory_windows
      REMOVE path_type
      REMOVE fme_geometry{0}
      REMOVE fme_geometry{}
    -> FeatureReader_3 [INITIATOR]
FeatureReader_3
    ATTRIBUTES = text_line,"text_line_data,fme_geometry{0}"
    ATTR_ACCUM_MODE = Merge Initiator and Result
    ATTR_CONFLICT_RES = Use Result
    ATTR_IGNORE_NULLS = No
    COMBINE_GEOM = Use Result
    DATASET = @Value(path_unix)
    FORMAT = TEXTLINE
    OUTPUT_FEATURES_DISPLAY = Schema and Data Features
    TEXTLINE_CREATE_FEATURE_TABLES_FROM_DATA = Yes
    TEXTLINE_ENCODING = utf-8
    TEXTLINE_READ_WHOLE_FILE_AT_ONCE = YES
    text_line -> TestFilter_2
TestFilter_2
    DEFAULT_VALUE = <UNFILTERED>
    TEST_LIST = "BOOL_OP,OR,COMPOSITE_TEST,""""""1"""""",TEST_CLAUSE,TEST $(DICTIONARY_TYPE) = XML",XML,"BOOL_OP,OR,COMPOSITE_TEST,""""""1"""""",TEST_CLAUSE,TEST $(DICTIONARY_TYPE) = JSON",JSON
    XML -> XMLTemplater [SUB]
    JSON -> JSONTemplater [SUB]
Creator
    GEOMTYPE = Geometry Object
    NUM = 1
    CREATED -> TestFilter
TestFilter
    DEFAULT_VALUE = <UNFILTERED>
    TEST_LIST = "BOOL_OP,OR,COMPOSITE_TEST,""""""1"""""",TEST_CLAUSE,TEST $(DICTIONARY_TYPE) = XML",XML,"BOOL_OP,OR,COMPOSITE_TEST,""""""1"""""",TEST_CLAUSE,TEST $(DICTIONARY_TYPE) = JSON",JSON
    XML -> XMLTemplater [ROOT]
    JSON -> JSONTemplater [ROOT]
Note: コード->文字列変換用 / 辞書XML作成
XMLTemplater
    OUTPUT_XML_HEADER = Yes
    RESULT_ATTRIBUTE = _codelists
    ROOT_QUERY_EXPR:
      <dictionaries name="codeLists">{
          fme:process-features("SUB")
      }</dictionaries>
    SUB_QUERY_EXPR:
      declare namespace gml="http://www.opengis.net/gml";
      <dictionary name="{fme:get-attribute("_codelist_name")}">{
          let $doc := fme:get-xml-attribute('text_line_data')
          for $d in $doc//gml:Definition
          let $key := data($d/gml:name)
          where $key
          return
          <item key="{$key}">{
              data($d/gml:description)
          }</item>
      }</dictionary>
    VISIBLE_QUERY_VALIDATE = Yes
    -> Dictionary (output)
Note: コード->文字列変換用 / 辞書JSON作成
JSONTemplater
    RESULT_ATTRIBUTE = _codelists
    ROOT_QUERY_EXPR:
      {|
          fme:process-features("SUB")
      |}
    SUB_QUERY_EXPR:
      declare namespace gml="http://www.opengis.net/gml";
      {
          fme:get-attribute("_codelist_name") : [
              let $doc := fme:get-xml-attribute('text_line_data')
              for $d in $doc//gml:Definition
              let $key := data($d/gml:name)
              where $key
              return
              {
                  "key" : {$key},
                  "value" : {data($d/gml:description)}
              }
          ]
      }
    VISIBLE_QUERY_VALIDATE = Yes
    -> Dictionary (output)
Dictionary (output)

Bookmark: ファイル名を lower case に変更
StringCaseChanger
    ATTRCHOICE = Selected Attributes
    ATTRLIST = path_filename
    CHANGE_TYPE = lowercase
    -> FeatureMerger [REQUESTOR]
StringCaseChanger_2
    ATTRCHOICE = Selected Attributes
    ATTRLIST = path_filename
    CHANGE_TYPE = lowercase
    -> FeatureMerger [SUPPLIER]

FME custom transformer FilePathExtractor

Parameters:
- DIRECTORY =   # Directory

Input (input)
    -> FeatureReader [INITIATOR]
FeatureReader
    ATTRIBUTES = PATH,"path_unix,path_windows,path_rootname,path_filename,path_extension,path_filesize,path_ownername,path_readonly,path_modified_date,path_created_date,path_accessed_date,path_directory_unix,path_directory_windows,path_type,fme_geometry{0}"
    ATTR_ACCUM_MODE = Only Use Result
    COMBINE_GEOM = Use Result
    DATASET = $(DIRECTORY)
    FORMAT = PATH
    OUTPUT_FEATURES_DISPLAY = Schema and Data Features
    PATH_GLOB_PATTERN = *
    PATH_NO_EMPTY_PROPERTIES = YES
    PATH_RECURSE_DIRECTORIES = NO
    PATH_RETRIEVE_FILE_PROPERTIES = NO
    PATH_TYPE = FILE
    PATH -> Tester
Tester
    BOOL_OP = OR
    COMPOSITE_TEST = 1
    TEST_CLAUSE = TEST @Value(path_extension) = zip
    TEST_MODE = TEST
    PASSED -> FeatureReader_2 [INITIATOR]
    FAILED -> Output (output)
FeatureReader_2
    ATTRIBUTES = PATH,"path_unix,path_windows,path_rootname,path_filename,path_extension,path_filesize,path_ownername,path_readonly,path_modified_date,path_created_date,path_accessed_date,path_directory_unix,path_directory_windows,path_type,fme_geometry{0}"
    ATTR_ACCUM_MODE = Only Use Result
    COMBINE_GEOM = Use Result
    DATASET = @Value(path_unix)
    FORMAT = PATH
    OUTPUT_FEATURES_DISPLAY = Schema and Data Features
    PATH_GLOB_PATTERN = *
    PATH_NO_EMPTY_PROPERTIES = YES
    PATH_RECURSE_DIRECTORIES = NO
    PATH_RETRIEVE_FILE_PROPERTIES = NO
    PATH_TYPE = FILE
    PATH -> Output (output)
Output (output)

FME workspace CityGML建築物の3DTiles変換_東京23区_runner.fmw

Parameters:
- MESHCODE_LIST_CSV_FOLDER = $(FME_MF_DIR)resources\地域別メッシュコードリスト\東京23区   # 地域別メッシュコードリスト（CSV）フォルダー
- CITYCML_BLDG_FOLDER = C:\Users\takas\PSS Dropbox\All_Project\20200001_mri_digitaltwin\05_citygml\東京23区+八王子（南大沢）\20210215_東京23区データ更新\13100_東京23区\udx\bldg   # CityGML建築物データフォルダー
- STANDARD_CODELIST_FOLDER = $(FME_MF_DIR)resources\標準製品仕様_コードリスト   # 標準コードリスト（XML）保存先フォルダー
- CUSTOM_CODELIST_FOLDER = C:\Users\takas\PSS Dropbox\All_Project\20200001_mri_digitaltwin\05_citygml\東京23区+八王子（南大沢）\20210215_東京23区データ更新\13100_東京23区\codelists   # カスタムコードリスト（XML）保存先フォルダー
- BLDG_SCHEMA_XLSXR = $(FME_MF_DIR)resources\スキーマ定義\20210128_東京23区3DTiles建物属性.xlsx   # 建築物スキーマ定義テーブル（Excel）
- DEST_FOLDER_CESIUM3DTILES = $(FME_MF_DIR)20210216_東京23区変換結果   # 3DTiles出力先フォルダー
- LOG_FOLDER = $(FME_MF_DIR)logs_20210216   # ログファイル出力先フォルダー
- MAX_PROC = 6   # Maximum Number of Concurrent FME Processes (1-7)

Readers:
- PATH_1: PATH from $(MESHCODE_LIST_CSV_FOLDER)

PATH (reader PATH_1)
    attributes: path_unix buffer, path_windows buffer, path_rootname buffer, path_filename buffer, path_extension buffer, path_filesize buffer, path_ownername buffer, path_readonly buffer, path_modified_date date, path_created_date date, path_accessed_date date, path_directory_unix buffer, path_directory_windows buffer, path_type char(10)
    -> AttributeCreator
AttributeCreator
    ATTR_TABLE = SET_TO _log_file = $(LOG_FOLDER)/@Value(path_rootname).log
    -> WorkspaceRunner
WorkspaceRunner
    BLOCKING = No
    MAX_PROC = $(MAX_PROC)
    MAX_TO_BATCH = 1
    WORKSPACE_FILE = $(FME_MF_DIR)CityGML建築物の3DTiles変換_東京23区.fmw
    WORKSPACE_PARAMETERS = SOURCE_CITYGML_BLD_FOLDER,$(CITYCML_BLDG_FOLDER),MESHCODE_LIST_CSV,$(MESHCODE_LIST_CSV_FOLDER),STANDARD_CODELIST_FOLDER,$(STANDARD_CODELIST_FOLDER),CUSTOM_CODELIST_FOLDER,$(CUSTOM_CODELIST_FOLDER),SCHEMA_DEFINITION_EXCEL,$(BLDG_SCHEMA_XLSXR),DEST_3DTILES_FOLDER,$(DEST_FOLDER_CESIUM3DTILES),DEST_3DTILESET_NAME,@Value(path_rootname),LOG_FILE,@Value(_log_file)

FME workspace CityGML建築物の3DTiles変換_東京23区.fmw

Parameters:
- SOURCE_CITYGML_BLD_FOLDER = C:\Users\takas\PSS Dropbox\All_Project\20200001_mri_digitaltwin\03_受領データ整理\東京23区+南大沢\20210129_国際航業納品\13100_東京23区\citygml\13100\udx\bldg   # CityGML建築物データフォルダー
- MESHCODE_LIST_CSV = $(FME_MF_DIR)resources\地域別メッシュコードリスト\東京23区\13101_chiyoda-ku.csv   # 対象地域の3次メッシュコードリスト（CSV）
- STANDARD_CODELIST_FOLDER = $(FME_MF_DIR)resources\標準製品仕様_コードリスト   # 標準コードリスト（XML）保存先フォルダー
- CUSTOM_CODELIST_FOLDER = C:\Users\takas\PSS Dropbox\All_Project\20200001_mri_digitaltwin\03_受領データ整理\東京23区+南大沢\20210129_国際航業納品\13100_東京23区\citygml\13100\codelists   # カスタムコードリスト（XML）保存先フォルダー
- SCHEMA_DEFINITION_EXCEL = $(FME_MF_DIR)resources\スキーマ定義\20210128_東京23区3DTiles建物属性.xlsx   # 建築物スキーマ定義テーブル（Excel）
- DEST_3DTILES_FOLDER = $(FME_MF_DIR)20210210_東京23区建物3DTiles変換結果   # 3DTiles出力先フォルダー
- DEST_3DTILESET_NAME = 13101_chiyoda-ku   # 3DTilesタイルセット名
- LOG_FILE = $(FME_MF_DIR)logs_20210210\13122_katsushika-ku.log   # Log File

Readers:
- XLSXR_1: XLSXR from $(SCHEMA_DEFINITION_EXCEL)
- PATH_1: PATH from $(STANDARD_CODELIST_FOLDER)
- PATH_2: PATH from $(CUSTOM_CODELIST_FOLDER)
- CSV2_1: CSV2 from $(MESHCODE_LIST_CSV)
- PATH_3: PATH from $(SOURCE_CITYGML_BLD_FOLDER)

Writers:
- CESIUM3DTILES_1: CESIUM3DTILES to $(DEST_3DTILES_FOLDER)
- CSV2_2: CSV2 to $(DEST_3DTILES_FOLDER)
- CSV2_3: CSV2 to $(DEST_3DTILES_FOLDER)

Note: カスタムコードリスト [PATH]
PATH (reader PATH_2)
    attributes: path_unix buffer, path_windows buffer, path_rootname buffer, path_filename buffer, path_extension buffer, path_filesize buffer, path_ownername buffer, path_readonly buffer, path_modified_date date, path_created_date date, path_accessed_date date, path_directory_unix buffer, path_directory_windows buffer, path_type char(10)
    -> FeatureMerger [REQUESTOR]
Note: 標準コードリスト [PATH]
PATH (reader PATH_1)
    attributes: path_unix buffer, path_windows buffer, path_rootname buffer, path_filename buffer, path_extension buffer, path_filesize buffer, path_ownername buffer, path_readonly buffer, path_modified_date date, path_created_date date, path_accessed_date date, path_directory_unix buffer, path_directory_windows buffer, path_type char(10)
    -> FeatureMerger [SUPPLIER]
FeatureMerger
    ATTR_ACCUM_MODE = Merge Supplier
    ATTR_CONFLICT_RES = Use Requestor
    IGNORE_NULLS = No
    JOIN_KEYS = @Value(path_rootname) @Value(path_rootname) AUTO
    MERGE_TYPE = Attributes Only
    PROCESS_DUPS = NO
    REJECT_NULL_MISSING_KEYS = No
    SUPPLIERS_FIRST = No
    MERGED -> AttributeKeeper_4
    UNMERGED_REQUESTOR -> AttributeKeeper_4
    UNUSED_SUPPLIER -> AttributeKeeper_4
AttributeKeeper_4
    CREATE_BULK_MODE_FEATURES = NO
    KEEP_ATTRS = path_filename,path_unix
    -> Tester
Note: 暫定対応 / Exclude / Common_localPublicAuthorities.xml
Tester
    BOOL_OP = OR
    COMPOSITE_TEST = 1
    TEST_CLAUSE = TEST @Value(path_filename) != Common_localPublicAuthorities.xml
    TEST_MODE = TEST
    PASSED -> FeatureReader [INITIATOR]
FeatureReader
    ATTRIBUTES = text_line,"text_line_data,fme_geometry{0}"
    ATTR_ACCUM_MODE = Merge Initiator and Result
    ATTR_CONFLICT_RES = Use Result
    ATTR_IGNORE_NULLS = No
    COMBINE_GEOM = Use Result
    DATASET = @Value(path_unix)
    FORMAT = TEXTLINE
    OUTPUT_FEATURES_DISPLAY = Schema and Data Features
    TEXTLINE_CREATE_FEATURE_TABLES_FROM_DATA = Yes
    TEXTLINE_ENCODING = utf-8
    TEXTLINE_READ_WHOLE_FILE_AT_ONCE = YES
    text_line -> XMLTemplater [SUB]
PATH (reader PATH_3)
    attributes: path_unix buffer, path_windows buffer, path_rootname buffer, path_filename buffer, path_extension buffer, path_filesize buffer, path_ownername buffer, path_readonly buffer, path_modified_date date, path_created_date date, path_accessed_date date, path_directory_unix buffer, path_directory_windows buffer, path_type char(10)
    -> StringSearcher
StringSearcher
    CASE = no
    MATCHED_RESULT_ATTR = meshcode
    REGEXP = \d{8}
    STRING_TO_SEARCH = @Value(path_rootname)
    MATCHED -> FeatureMerger_6 [REQUESTOR]
Note: 対象地域の3次メッシュコードリスト / [CSV2]
13101_chiyoda-ku (reader CSV2_1)
    attributes: index string, city_code string, city_name string, meshcode string
    -> FeatureMerger_6 [SUPPLIER]
FeatureMerger_6
    ATTR_ACCUM_MODE = Merge Supplier
    ATTR_CONFLICT_RES = Use Requestor
    IGNORE_NULLS = No
    JOIN_KEYS = @Value(meshcode) @Value(meshcode) AUTO
    MERGE_TYPE = Attributes Only
    PROCESS_DUPS = NO
    REJECT_NULL_MISSING_KEYS = No
    SUPPLIERS_FIRST = No
    MERGED -> Sorter_2
Sorter_2
    SORT_PARM = meshcode NUMERIC ASCENDING
    SORTED -> AttributeKeeper_6
AttributeKeeper_6
    CREATE_BULK_MODE_FEATURES = NO
    KEEP_ATTRS = path_unix
    -> FeatureReader_2 [INITIATOR]
    -> FeatureReader_3 [INITIATOR]
Note: [CITYGML] / LODs to Read: LOD1, LOD2 / GML SRS Axix Order: 2,1,3
FeatureReader_2
    ATTRS_TO_EXPOSE = gml_id gml_parent_id fme_basename
    ATTR_ACCUM_MODE = Only Use Result
    CITYGML_ADD_NAMESPACE_PREFIX_TO_FEATURE_TYPES = No
    CITYGML_CITYGML_EXPOSE_FORMAT_ATTRS = fme_basename,xml_char(50)
    CITYGML_GENERIC_ATTRS_AS_FEATURES = No
    CITYGML_GENERIC_ATTRS_AS_SCHEMA_ATTRS = Yes
    CITYGML_LODS_TO_READ = 1 2
    CITYGML_MATERIAL_FEATURES = No
    CITYGML_MAX_ATTRIBUTES_PER_NESTED_ATTRIBUTE = 400
    CITYGML_ONLY_FEATURE_TYPES_IN_DATASET = YES
    CITYGML_SKIP_SCHEMA_LOCATION_IN_DATASET = No
    CITYGML_SRS_AXIS_ORDER = 2,1,3
    CITYGML_TEXTURE_COORDINATES_ORDER_FIX = No
    CITYGML_USE_CITYGML_SCHEMA_FILES = Yes
    CITYGML_USE_SEARCH_ENVELOPE = NO
    CITYGML_USE_XLINK_HREF_GEOMETRY_TRAITS = Yes
    CITYGML_VALIDATE_DATASET = no
    COMBINE_GEOM = Use Result
    DATASET = @Value(path_unix)
    FORMAT = CITYGML
    INTERACT = <No Spatial Filter>
    OUTPUT_FEATURES_DISPLAY = Schema and Data Features
    <OTHER> -> FeatureTypeFilter
    <REJECTED> -> Junction_4
FeatureTypeFilter
    ATTRIBUTES = Building,BuildingInstallation,Address,CityModel,<Blank>,<Unfiltered>,Room
    Building -> AttributeCreator
    BuildingInstallation -> AttributeCreator_2
    <UNFILTERED> -> GeometryFilter
AttributeCreator
    ATTR_TABLE = SET_TO _building_id = @Value(gml_id)
    -> AttributeKeeper
AttributeKeeper
    CREATE_BULK_MODE_FEATURES = NO
    KEEP_ATTRS = _building_id,fme_basename,gml_id,gml_parent_id
    -> Sorter
AttributeCreator_2
    ATTR_TABLE = SET_TO _building_id = @Value(gml_parent_id)
    -> AttributeKeeper_2
AttributeKeeper_2
    CREATE_BULK_MODE_FEATURES = NO
    KEEP_ATTRS = _building_id,gml_id,fme_basename
    -> Sorter
Sorter
    GROUP_BY = fme_basename
    SORT_PARM = _building_id ALPHA ASCENDING
    SORTED -> FeatureMerger_2 [REQUESTOR]
GeometryFilter
    BREAK_AGG = No
    GEOM_PORT_NAMES = Surface
    SURFACE -> AttributeKeeper_3
AttributeKeeper_3
    CREATE_BULK_MODE_FEATURES = NO
    KEEP_ATTRS = gml_parent_id,gml_id,fme_basename
    -> FeatureMerger_2 [SUPPLIER]
FeatureMerger_2
    GEOM_TYPE = Build Aggregates
    GROUP_BY = fme_basename
    JOIN_KEYS = @Value(gml_id) @Value(gml_parent_id) AUTO
    MERGE_TYPE = Geometry
    PROCESS_DUPS = YES
    REJECT_NULL_MISSING_KEYS = No
    SUPPLIERS_FIRST = No
    MERGED -> Aggregator
    UNMERGED_REQUESTOR -> GeometryValidator
Aggregator
    ACCUM_ATTRS_NAME = Merge Incoming Attributes
    AGGREGATE_TYPE = Homogeneous Collection (If Possible)
    GROUP_BY = _building_id fme_basename
    MODE = Geometry - Assemble One Level
    SEP = ,
    AGGREGATE -> AttributeCreator_3
AttributeCreator_3
    ATTR_TABLE:
      SET_TO _lod = 2
      SET_TO LOD2 = 1
    -> Junction_6
GeometryValidator
    ISSUE_ATTR_NAME = _issues
    PRESETS = Surfaces And Solids
    REPAIR = No
    RULES = SELF_INTERSECTING CHECK_HOLE_TOUCHING_POLYGON]No]CONNECT_Z_MODE_SI]FIRST_WINS]SELF_INTERSECTION_TOLERANCE]None]FME_CONTROLLER_QUERY_FILE]transformers\dependencies\geometryvalidator\SELF_INTERSECTING.fme PLANAR_SURFACE CHECK_AREA]DO_NOT_CHECK_AREA]TOLERANCE_MODE]AUTO]TOLERANCE]0.0]ANGULAR_TOLERANCE_MODE]AUTO]ANGULAR_TOLERANCE]0.0]FME_CONTROLLER_QUERY_FILE]transformers\dependencies\geometryvalidator\PLANAR_SURFACE.fme SOLID_VOID_REPAIR  SHELL_VALIDATION FLIP_APPEARANCE_MODE]FLIP_APPEARANCES]FME_CONTROLLER_QUERY_FILE]transformers\dependencies\geometryvalidator\SHELL_VALIDATION.fme MISSING_TEXTURE_COORDINATES  SURFACE_ORIENTATION  SOLID_ORIENTATION
    SUMMARY = Detailed
    PASSED -> AttributeCreator_4
    FAILED -> ListConcatenator
AttributeCreator_4
    ATTR_TABLE = SET_TO _lod = 1
    -> Junction_6
Junction_6
    -> FeatureMerger_5 [REQUESTOR]
ListConcatenator
    DROP_EMPTY_PARTS = No
    LIST_ATTR = _issues{}.issue_found
    SEP = ,
    VAL_ATTR = issues
    -> AttributeManager_2
AttributeManager_2
    ATTR_TABLE:
      RENAME_SET_VALUE fme_basename > filename
      RENAME_SET_VALUE _building_id > building_id
      REMOVE gml_parent_id
      REMOVE _issues{}.count
      REMOVE _issues{}.issue_found
      REMOVE _issues{}.location_sample.x
      REMOVE _issues{}.location_sample.y
      REMOVE _issues{}.location_sample.z
      REMOVE _issues{}.repair_state
    -> failed_buildings (writer CSV2_2)
failed_buildings (writer CSV2_2)
    attributes: filename string, gml_id string, building_id string, issues string
Junction_4
Note: CityGMLデータを単一の / テキスト（XML）として読み込む
FeatureReader_3
    ATTRIBUTES = text_line,"text_line_data,fme_geometry{0},fme_basename"
    ATTR_ACCUM_MODE = Merge Initiator and Result
    ATTR_CONFLICT_RES = Use Result
    ATTR_IGNORE_NULLS = No
    COMBINE_GEOM = Use Result
    DATASET = @Value(path_unix)
    FORMAT = TEXTLINE
    OUTPUT_FEATURES_DISPLAY = Schema and Data Features
    TEXTLINE_CREATE_FEATURE_TABLES_FROM_DATA = Yes
    TEXTLINE_ENCODING = utf-8
    TEXTLINE_READ_WHOLE_FILE_AT_ONCE = YES
    TEXTLINE_TEXTLINE_EXPOSE_FORMAT_ATTRS = fme_basename,char(50)
    text_line -> FeatureMerger_3 [REQUESTOR]
    <REJECTED> -> Junction_5
Junction_5
Creator
    GEOMTYPE = Geometry Object
    NUM = 1
    CREATED -> XMLTemplater [ROOT]
Note: コード->文字列変換用 / 辞書XML作成
XMLTemplater
    OUTPUT_XML_HEADER = Yes
    RESULT_ATTRIBUTE = _code_lists
    ROOT_QUERY_EXPR:
      <dictionaries name="codeLists">{
          fme:process-features("SUB")
      }</dictionaries>
    SUB_QUERY_EXPR:
      declare namespace gml="http://www.opengis.net/gml";
      <dictionary name="{fme:get-attribute("path_filename")}">{
          let $doc := fme:get-xml-attribute('text_line_data')
          for $d in $doc//gml:Definition
          let $key := data($d/gml:name)
          where $key
          return
          <item key="{$key}">{
              data($d/gml:description)
          }</item>
      }</dictionary>
    VISIBLE_QUERY_VALIDATE = Yes
    -> XMLFormatter
XMLFormatter
    COLLAPSE_EMPTY_ELEMENT = No
    FORMATTING_CHOICE = Linearize XML
    LIST_NAME = _xml_error
    NAMESPACE_CLEANUP = No
    OUTPUT_ENCODING = utf-8
    REMOVE_ALL_COMMENT = No
    REMOVE_EMPTY_ELEMENT = No
    SCHEMALOC_CLEANUP = No
    WHITESPACE_HANDLING = Remove excess whitespace
    XML_ATTR_TEXT = _code_lists
    XML_INPUT_TYPE = Attribute Specifying XML Text
    XML_OUTPUT_ATTR = _code_lists
    XML_OUTPUT_TYPE = Attribute
    PASSED -> FeatureMerger_3 [SUPPLIER]
FeatureMerger_3
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> XMLXQueryUpdater
Note: コード -> 文字列変換
XMLXQueryUpdater
    QUERY_EXPR:
      declare namespace gml="http://www.opengis.net/gml";

      let $doc := fme:get-xml-attribute('_code_lists')
      for $x in //*[@codeSpace]
      let $dict := $doc//dictionary[@name = replace($x/@codeSpace, '.+/(.+?)$', '$1')]
      where $dict
      return
      replace value of node $x with data($dict/item[@key = data($x)])
    RESULT_ATTRIBUTE = text_line_data
    XML_ATTR = text_line_data
    XML_TYPE = Attribute specifying XML
    XQUERY_TYPE = XQuery expression
    QUERY_RESULTS -> VariableSetter
VariableSetter
    SCOPE = Local
    VALUE = @Value(fme_basename)
    VARNAME = vFmeBasename
    -> XMLFragmenter
XMLFragmenter
    ATTRIBUTE_XML = text_line_data
    EMBEDDED_EXPRESSIONS = Building
    FEATURE_TYPES_FORMAT_NAME = XML
    MERGE_ATTRS = No
    REJECT_FEATURES_WITH_NO_FRAGMENTS = YES
    XML_SOURCE_TYPE = Attribute with XML document
    FRAGMENTS -> VariableRetriever
VariableRetriever
    SCOPE = Local
    VALUE_ATTR = fme_basename
    VARNAME = vFmeBasename
    -> AttributeKeeper_5
AttributeKeeper_5
    CREATE_BULK_MODE_FEATURES = NO
    KEEP_ATTRS = fme_basename,xml_fragment
    -> FeatureMerger_4 [REQUESTOR]
Sampler
    RATE = 2
    SAMPLE_MODE = No
    SAMPLE_TYPE_LONG = First N Features
建築物 (reader XLSXR_1)
    attributes: group string, tag char(40), prefix char(5), category char(35), attribute char(48), datatype char(7), target number(2,0)
    -> Tester_2
Tester_2
    BOOL_OP = COMPOSITE
    COMPOSITE_TEST = 1 AND 2
    TEST_CLAUSE:
      TEST target ATTRIBUTE_HAS_A_VALUE ""
      TEST attribute ATTRIBUTE_HAS_A_VALUE ""
    TEST_MODE = TEST
    PASSED -> NullAttributeMapper
NullAttributeMapper
    ATTRCHOICE = Selected Attributes
    ATTRLIST = attribute category datatype prefix tag target
    NULL_TREATMENT = Empty String
    SOURCE_ATTR_VAL = "Missing (Selected Attributes Only)"
    -> AttributeManager
AttributeManager
    ATTR_TABLE:
      SET_TO name = @ReplaceString(@Value(prefix)_@Value(category)_@Value(attribute),__,_)
      SET_TO fme_data_type = fme_@Value(datatype)
      REMOVE prefix
      REMOVE category
      REMOVE attribute
      REMOVE datatype
      REMOVE target
    -> ListBuilder
ListBuilder
    LIST_ATTRS_TO_INCLUDE = fme_data_type name tag
    LIST_NAME = attribute
    -> XMLTemplater_2 [ROOT]
XMLTemplater_2
    OUTPUT_XML_HEADER = Yes
    RESULT_ATTRIBUTE = _tag_to_attr
    ROOT_QUERY_EXPR:
      <dictionary name="tagToAttr">{
          let $tags := fme:get-list-attribute('attribute{}.tag')
          let $names := fme:get-list-attribute('attribute{}.name')
          for $i in (1 to count($tags))
          where $tags[$i]
          return <item key="{$tags[$i]}">{$names[$i]}</item>
      }</dictionary>
    VISIBLE_QUERY_VALIDATE = Yes
    -> FeatureMerger_4 [SUPPLIER]
FeatureMerger_4
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> XMLXQueryExtractor
XMLXQueryExtractor
    NEW_ATTRIBUTES = gml_id
    QUERY_EXPR:
      declare namespace gml="http://www.opengis.net/gml";
      declare namespace bldg="http://www.opengis.net/citygml/building/2.0";
      declare namespace gen="http://www.opengis.net/citygml/generics/2.0";
      declare namespace uro="http://www.kantei.go.jp/jp/singi/tiiki/toshisaisei/itoshisaisei/iur/uro/1.4";
      declare namespace xAL="urn:oasis:names:tc:ciq:xsdschema:xAL:2.0";

      fme:set-attribute('gml_id', xs:string(/bldg:Building/@gml:id))
      ,
      let $dict := fme:get-xml-attribute('_tag_to_attr')
      for $x in /bldg:Building/*
      let $tag1 := name($x)
      return
      if ($tag1 = 'uro:extendedAttribute') then
      {
          fme:set-attribute('uro_拡張_'||data($x//uro:key), data($x//uro:codeValue))
      }
      else if ($tag1 = 'bldg:address') then
      {
          fme:set-attribute('bldg_住所', data($x//xAL:Address))
      }
      else if ($tag1 = 'uro:buildingDetails') then
      {
          for $y in $x/uro:BuildingDetails/*
          let $tag2 := name($y)
          let $attr := $dict//item[@key = $tag2]
          where $attr
          return
          {
              fme:set-attribute(data($attr), data($y))
          }
      }
      else if ($tag1 = 'uro:largeCustomerFacilities') then
      {
          (: pass :)
      }
      else if ($tag1 = 'gen:genericAttributeSet') then
      {
          let $prefix := 'gen_'||$x/@name||'_'
          for $y in $x/*
          return
          {
              fme:set-attribute($prefix||$y/@name, data($y/gen:value))
          }
      }
      else if (starts-with($tag1, 'gen:')) then
      {
          fme:set-attribute('gen_'||$x/@name, data($x/gen:value))
      }
      else
      {
          let $attr := $dict//item[@key = $tag1]
          return
          if ($attr) then
          {
              fme:set-attribute(data($attr), data($x))
          }
          else ()
      }
    RESULT_ATTRIBUTE = _result
    RESULT_TYPE_NAME = Separated values
    SEPARATOR_VALUE = ,
    WRITE_XML_HEADER = No
    XML_ATTR = xml_fragment
    XML_REMOVE_SOURCE_ATTR = No
    XML_TYPE = Attribute specifying XML
    XQUERY_TYPE = XQuery expression
    QUERY_RESULTS -> AttributeRemover
AttributeRemover
    REMOVE_ATTRS = _result,_tag_to_attr,xml_fragment
    -> Junction
Note: FeatureMerger_5 : Supplier
Junction
    -> Junction_2
Note: AttributeRemover : Output
Junction_2
    -> AttributeExposer_2
AttributeExposer_2
    ATTR_LIST = uro_建物利用現況_市区町村
    -> FeatureMerger_7 [REQUESTOR]
Creator_2
    GEOMTYPE = Geometry Object
    NUM = 1
    CREATED -> ParameterFetcher_2
ParameterFetcher_2
    ATTR_LIST = _city_code $(DEST_3DTILESET_NAME)
    -> SubstringExtractor
SubstringExtractor
    END = 4
    RESULT_ATTR = _city_code
    SRC_STRING = @Value(_city_code)
    START = 0
    -> FeatureMerger_7 [SUPPLIER]
Note: 暫定対応 / タイルセット名から市区町村コードを抽出 / 該当する建物に絞る
FeatureMerger_7
    ATTR_ACCUM_MODE = Merge Supplier
    ATTR_CONFLICT_RES = Use Requestor
    IGNORE_NULLS = No
    JOIN_KEYS = @Value(uro_建物利用現況_市区町村) @Value(_city_code) AUTO
    MERGE_TYPE = Attributes Only
    PROCESS_DUPS = NO
    REJECT_NULL_MISSING_KEYS = No
    SUPPLIERS_FIRST = No
    MERGED -> FeatureMerger_5 [SUPPLIER]
Note: 属性の結合
FeatureMerger_5
    ATTR_ACCUM_MODE = Merge Supplier
    ATTR_CONFLICT_RES = Use Requestor
    GROUP_BY = fme_basename
    IGNORE_NULLS = No
    JOIN_KEYS = @Value(gml_id) @Value(gml_id) AUTO
    MERGE_TYPE = Attributes Only
    PROCESS_DUPS = NO
    REJECT_NULL_MISSING_KEYS = No
    SUPPLIERS_FIRST = No
    MERGED -> ParameterFetcher
ParameterFetcher
    ATTR_LIST = fme_feature_type $(DEST_3DTILESET_NAME)
    -> AttributeExposer
Note: 出現する属性名を現わす
AttributeExposer
    ATTR_LIST = gen_荒川洪水浸水想定区域（計画規模）_浸水ランク,gen_荒川洪水浸水想定区域（計画規模）_浸水深,gen_荒川洪水浸水想定区域（計画規模）_継続時間,gen_荒川洪水浸水想定区域（想定最大規模）_浸水ランク,gen_荒川洪水浸水想定区域（想定最大規模）_浸水深,gen_荒川洪水浸水想定区域（想定最大規模）_継続時間,gen_江戸川洪水浸水想定区域（計画規模）_浸水ランク,gen_江戸川洪水浸水想定区域（計画規模）_浸水深,gen_江戸川洪水浸水想定区域（計画規模）_継続時間,gen_江戸川洪水浸水想定区域（想定最大規模）_浸水ランク,gen_江戸川洪水浸水想定区域（想定最大規模）_浸水深,gen_江戸川洪水浸水想定区域（想定最大規模）_継続時間,gen_利根川洪水浸水想定区域（計画規模）_浸水ランク,gen_利根川洪水浸水想定区域（計画規模）_浸水深,gen_利根川洪水浸水想定区域（計画規模）_継続時間,gen_利根川洪水浸水想定区域（想定最大規模）_浸水ランク,gen_利根川洪水浸水想定区域（想定最大規模）_浸水深,gen_利根川洪水浸水想定区域（想定最大規模）_継続時間,gen_多摩川洪水浸水想定区域（計画規模）_浸水ランク,gen_多摩川洪水浸水想定区域（計画規模）_浸水深,gen_多摩川洪水浸水想定区域（計画規模）_継続時間,gen_多摩川洪水浸水想定区域（想定最大規模）_浸水ランク,gen_多摩川洪水浸水想定区域（想定最大規模）_浸水深,gen_多摩川洪水浸水想定区域（想定最大規模）_継続時間,gen_神田川洪水浸水想定区域（想定最大規模）_浸水ランク,gen_神田川洪水浸水想定区域（想定最大規模）_浸水深,gen_神田川洪水浸水想定区域（想定最大規模）_継続時間,gen_石神井川及び白子川流域洪水浸水想定区域（想定最大規模）_浸水ランク,gen_石神井川及び白子川流域洪水浸水想定区域（想定最大規模）_浸水深,gen_石神井川及び白子川流域洪水浸水想定区域（想定最大規模）_継続時間,gen_江東内部河川流域洪水浸水想定区域（想定最大規模）_浸水ランク,gen_江東内部河川流域洪水浸水想定区域（想定最大規模）_浸水深,gen_江東内部河川流域洪水浸水想定区域（想定最大規模）_継続時間,gen_城南地区河川流域洪水浸水想定区域（想定最大規模）_浸水ランク,gen_城南地区河川流域洪水浸水想定区域（想定最大規模）_浸水深,gen_城南地区河川流域洪水浸水想定区域（想定最大規模）_継続時間,gen_野川、仙川、入間川、谷沢川及び丸子川流域洪水浸水想定区域（想定最大規模）_浸水ランク,gen_野川、仙川、入間川、谷沢川及び丸子川流域洪水浸水想定区域（想定最大規模）_浸水深,gen_野川、仙川、入間川、谷沢川及び丸子川流域洪水浸水想定区域（想定最大規模）_継続時間,gen_Case2水門開放津波浸水想定_説明,gen_Case2水門開放津波浸水想定_浸水ランク,gen_Case2水門開放津波浸水想定_浸水深,gen_Case2水門閉鎖津波浸水想定_説明,gen_Case2水門閉鎖津波浸水想定_浸水ランク,gen_Case2水門閉鎖津波浸水想定_浸水深,gen_土砂災害警戒区域_区域区分,gen_土砂災害警戒区域_現象区分,bldg_計測高さ,gen_平成28年度建物利用現況_建物地上階数,gen_平成28年度建物利用現況_建物地下階数,gen_平成28年度建物利用現況_図形面積,gen_平成28年度建物利用現況_建物構造コード,gen_平成28年度建物利用現況_延べ面積換算係数,gen_平成28年度建物利用現況_区市町村名称,gen_平成28年度建物利用現況_町丁目名称,uro_拡張_建物用途コード（都道府県）,gen_地域地区,gen_地区計画,L1_MaxRank,L1_MaxDepth,L2_MaxRank,L2_MaxDepth
    -> StringPairReplacer
StringPairReplacer
    CASE = no
    MAP = "11 \"耐火構造\"\n12 \"準耐火造\"\n21 \"防火造\"\n22 \"木造\"\n"
    SRC_ATTRS = gen_平成28年度建物利用現況_建物構造コード
    -> AttributeSplitter
AttributeSplitter
    ATTR_NAME = gen_地域地区
    DELIMITER = ,
    DROP_EMPTY_PARTS = No
    LIST_NAME = _list
    TRIM_OPTION = Both
    -> AttributeRenamer
AttributeRenamer
    ATTR_TABLE:
      RENAME_SET_DEFAULT _list{0} > _district_or_zone_0
      RENAME_SET_DEFAULT _list{1} > _district_or_zone_1
      RENAME_SET_DEFAULT _list{2} > _district_or_zone_2
    -> StringPairReplacer_2
StringPairReplacer_2
    CASE = no
    MAP:
      41 "航空機騒音障害防止特別地区"
      40 "航空機騒音障害防止地区"
      39 "伝統的建造物群保存地区"
      38 "生産緑地地区"
      37 "流通業務地区"
      36 "緑化地域"
      35 "特別緑地保存地区"
      34 "緑地保全地域"
      33 "第2種歴史的風土保全地区"
      32 "第1種歴史的風土保全地区"
      31 "歴史的風土特別保存地区"
      30 "臨港地区"
      29 "駐車場整備地区"
      28 "風致地区"
      27 "景観地区"
      26 "特定防災街区整備地区"
      25 "準防火地域"
      24 "防火地域"
      23 "特定用途誘導地区"
      22 "居住調整地域"
      21 "都市再生特別地区"
      20 "特定街区"
      19 "高度利用地区"
      18 "高度地区"
      17 "高層住居誘導地区"
      16 "特例容積率適用地区"
      15 "特定用途制限地域"
      14 "特別用途地区"
      13 "工業専用地域"
      12 "工業地域"
      11 "準工業地域"
      10 "商業地域"
      9 "近隣商業地域"
      8 "田園住居地域"
      7 "準住居地域"
      6 "第2種住居地域"
      5 "第1種住居地域"
      4 "第2種中高層住居専用地域"
      3 "第1種中高層住居専用地域"
      2 "第2種低層住居専用地域"
      1 "第1種低層住居専用地域"
      0 "用途地域の指定をしない区域"
    SRC_ATTRS = _district_or_zone_0 _district_or_zone_1 _district_or_zone_2
    -> AttributeManager_3
AttributeManager_3
    ATTR_TABLE:
      RENAME_SET_VALUE bldg_計測高さ > 計測高さ
      RENAME_SET_VALUE gen_平成28年度建物利用現況_図形面積 > 図形面積
      RENAME_SET_VALUE gen_平成28年度建物利用現況_建物地上階数 > 建物地上階数
      RENAME_SET_VALUE gen_平成28年度建物利用現況_建物地下階数 > 建物地下階数
      RENAME_SET_VALUE gen_平成28年度建物利用現況_建物構造コード > 建物構造
      RENAME_SET_VALUE uro_拡張_建物用途コード（都道府県） > 建物用途
      RENAME_SET_VALUE gen_平成28年度建物利用現況_延べ面積換算係数 > 延べ面積換算係数
      SET_TO 住所 = @Value(gen_平成28年度建物利用現況_区市町村名称)@Value(gen_平成28年度建物利用現況_町丁目名称)
      REMOVE gen_平成28年度建物利用現況_区市町村名称
      REMOVE gen_平成28年度建物利用現況_町丁目名称
      REMOVE gen_地域地区
      RENAME_SET_VALUE _district_or_zone_0 > 用途地域
      RENAME_SET_VALUE _district_or_zone_1 > 高度地区
      RENAME_SET_VALUE _district_or_zone_2 > 防火及び準防火地域
      REMOVE _list{}
      RENAME_SET_VALUE gen_地区計画 > 地区計画
      RENAME_SET_VALUE gen_Case2水門開放津波浸水想定_説明 > Case2水門開放津波浸水想定_説明
      RENAME_SET_VALUE gen_Case2水門開放津波浸水想定_浸水ランク > Case2水門開放津波浸水想定_浸水ランク
      RENAME_SET_VALUE gen_Case2水門開放津波浸水想定_浸水深 > Case2水門開放津波浸水想定_浸水深
      RENAME_SET_VALUE gen_Case2水門閉鎖津波浸水想定_説明 > Case2水門閉鎖津波浸水想定_説明
      RENAME_SET_VALUE gen_Case2水門閉鎖津波浸水想定_浸水ランク > Case2水門閉鎖津波浸水想定_浸水ランク
      RENAME_SET_VALUE gen_Case2水門閉鎖津波浸水想定_浸水深 > Case2水門閉鎖津波浸水想定_浸水深
      RENAME_SET_VALUE gen_土砂災害警戒区域_区域区分 > 土砂災害警戒区域_区域区分
      RENAME_SET_VALUE gen_土砂災害警戒区域_現象区分 > 土砂災害警戒区域_現象区分
      RENAME_SET_VALUE _lod > LOD
      RENAME_SET_VALUE gml_id
      REMOVE _building_id
      REMOVE gml_parent_id
      REMOVE fme_basename
      REMOVE attribute{}.name
      REMOVE attribute{}.fme_data_type
      REMOVE attribute{}.tag
      REMOVE fme_feature_type
      REMOVE L1_MaxRank
      REMOVE L1_MaxDepth
      REMOVE L2_MaxRank
      REMOVE L2_MaxDepth
      REMOVE uro_建物利用現況_市区町村
      REMOVE _city_code
    -> BulkAttributeRenamer
BulkAttributeRenamer
    ATTRCHOICE = Selected Attributes
    ATTRLIST = gen_利根川洪水浸水想定区域（想定最大規模）_浸水ランク gen_利根川洪水浸水想定区域（想定最大規模）_浸水深 gen_利根川洪水浸水想定区域（想定最大規模）_継続時間 gen_利根川洪水浸水想定区域（計画規模）_浸水ランク gen_利根川洪水浸水想定区域（計画規模）_浸水深 gen_利根川洪水浸水想定区域（計画規模）_継続時間 gen_多摩川洪水浸水想定区域（想定最大規模）_浸水ランク gen_多摩川洪水浸水想定区域（想定最大規模）_浸水深 gen_多摩川洪水浸水想定区域（想定最大規模）_継続時間 gen_多摩川洪水浸水想定区域（計画規模）_浸水ランク gen_多摩川洪水浸水想定区域（計画規模）_浸水深 gen_多摩川洪水浸水想定区域（計画規模）_継続時間 gen_江戸川洪水浸水想定区域（想定最大規模）_浸水ランク gen_江戸川洪水浸水想定区域（想定最大規模）_浸水深 gen_江戸川洪水浸水想定区域（想定最大規模）_継続時間 gen_江戸川洪水浸水想定区域（計画規模）_浸水ランク gen_江戸川洪水浸水想定区域（計画規模）_浸水深 gen_江戸川洪水浸水想定区域（計画規模）_継続時間 gen_荒川洪水浸水想定区域（想定最大規模）_浸水ランク gen_荒川洪水浸水想定区域（想定最大規模）_浸水深 gen_荒川洪水浸水想定区域（想定最大規模）_継続時間 gen_荒川洪水浸水想定区域（計画規模）_浸水ランク gen_荒川洪水浸水想定区域（計画規模）_浸水深 gen_荒川洪水浸水想定区域（計画規模）_継続時間 gen_城南地区河川流域洪水浸水想定区域（想定最大規模）_浸水ランク gen_城南地区河川流域洪水浸水想定区域（想定最大規模）_浸水深 gen_城南地区河川流域洪水浸水想定区域（想定最大規模）_継続時間 gen_江東内部河川流域洪水浸水想定区域（想定最大規模）_浸水ランク gen_江東内部河川流域洪水浸水想定区域（想定最大規模）_浸水深 gen_江東内部河川流域洪水浸水想定区域（想定最大規模）_継続時間 gen_石神井川及び白子川流域洪水浸水想定区域（想定最大規模）_浸水ランク gen_石神井川及び白子川流域洪水浸水想定区域（想定最大規模）_浸水深 gen_石神井川及び白子川流域洪水浸水想定区域（想定最大規模）_継続時間 gen_神田川洪水浸水想定区域（想定最大規模）_浸水ランク gen_神田川洪水浸水想定区域（想定最大規模）_浸水深 gen_神田川洪水浸水想定区域（想定最大規模）_継続時間 gen_野川、仙川、入間川、谷沢川及び丸子川流域洪水浸水想定区域（想定最大規模）_浸水ランク gen_野川、仙川、入間川、谷沢川及び丸子川流域洪水浸水想定区域（想定最大規模）_浸水深 gen_野川、仙川、入間川、谷沢川及び丸子川流域洪水浸水想定区域（想定最大規模）_継続時間
    MODE_CHOICE = RENAME
    PATTERN_ACTION_DISP = PCREGEXPREPLACE
    REPLACE_PATTERN = ^gen_(.+)洪水浸水想定区域（(.+)）(_.+)$
    REPLACE_STR = \1洪水浸水想定_\2\3
    -> CsmapReprojector
Note: 標高 -> 楕円体高に変換
CsmapReprojector
    DEST = EPSG:4326
    GEOID_HEIGHT_GRID = $(FME_HOME)Reproject\GeoidHeightGrids\World\Egm96-Wgs84.gdc
    INTERPOLATION_TYPE_NAME = Nearest Neighbor
    RASTER_CELL_SIZE = Preserve Cells
    RASTER_TOLERANCE = 0.0
    VERTICAL_HANDLING = Orthometric height -> Geocentric or ellipsoid height
    REPROJECTED -> AppearanceRemover
    REPROJECTED -> tileset (writer CESIUM3DTILES_1)
    REPROJECTED -> attributes (writer CSV2_3)
AppearanceRemover
    SIDE_TO_REMOVE = Front and Back Sides
    -> Junction_3
    UNMATCHED -> Junction_3
Junction_3
    -> tileset00 (writer CESIUM3DTILES_1)
tileset00 (writer CESIUM3DTILES_1)
    attributes: 計測高さ float, 図形面積 float, 建物地上階数 int, 建物地下階数 int, 建物構造 string, 建物用途 string, 延べ面積換算係数 float, 住所 string, 用途地域 string, 高度地区 string, 防火及び準防火地域 string, 地区計画 string, 荒川洪水浸水想定_計画規模_浸水ランク int, 荒川洪水浸水想定_計画規模_浸水深 float, 荒川洪水浸水想定_計画規模_継続時間 float, 荒川洪水浸水想定_想定最大規模_浸水ランク int, 荒川洪水浸水想定_想定最大規模_浸水深 float, 荒川洪水浸水想定_想定最大規模_継続時間 float, 江戸川洪水浸水想定_計画規模_浸水ランク int, 江戸川洪水浸水想定_計画規模_浸水深 float, 江戸川洪水浸水想定_計画規模_継続時間 float, 江戸川洪水浸水想定_想定最大規模_浸水ランク int, 江戸川洪水浸水想定_想定最大規模_浸水深 float, 江戸川洪水浸水想定_想定最大規模_継続時間 float, 利根川洪水浸水想定_計画規模_浸水ランク int, 利根川洪水浸水想定_計画規模_浸水深 float, 利根川洪水浸水想定_計画規模_継続時間 float, 利根川洪水浸水想定_想定最大規模_浸水ランク int, 利根川洪水浸水想定_想定最大規模_浸水深 float, 利根川洪水浸水想定_想定最大規模_継続時間 float,
      多摩川洪水浸水想定_計画規模_浸水ランク int, 多摩川洪水浸水想定_計画規模_浸水深 float, 多摩川洪水浸水想定_計画規模_継続時間 float, 多摩川洪水浸水想定_想定最大規模_浸水ランク int, 多摩川洪水浸水想定_想定最大規模_浸水深 float, 多摩川洪水浸水想定_想定最大規模_継続時間 float, 神田川洪水浸水想定_想定最大規模_浸水ランク int, 神田川洪水浸水想定_想定最大規模_浸水深 float, 神田川洪水浸水想定_想定最大規模_継続時間 float, 石神井川及び白子川流域洪水浸水想定_想定最大規模_浸水ランク int, 石神井川及び白子川流域洪水浸水想定_想定最大規模_浸水深 float, 石神井川及び白子川流域洪水浸水想定_想定最大規模_継続時間 float, 江東内部河川流域洪水浸水想定_想定最大規模_浸水ランク int, 江東内部河川流域洪水浸水想定_想定最大規模_浸水深 float, 江東内部河川流域洪水浸水想定_想定最大規模_継続時間 float, 城南地区河川流域洪水浸水想定_想定最大規模_浸水ランク int, 城南地区河川流域洪水浸水想定_想定最大規模_浸水深 float, 城南地区河川流域洪水浸水想定_想定最大規模_継続時間 float, 野川、仙川、入間川、谷沢川及び丸子川流域洪水浸水想定_想定最大規模_浸水ランク int, 野川、仙川、入間川、谷沢川及び丸子川流域洪水浸水想定_想定最大規模_浸水深 float, 野川、仙川、入間川、谷沢川及び丸子川流域洪水浸水想定_想定最大規模_継続時間 float, Case2水門開放津波浸水想定_説明 string, Case2水門開放津波浸水想定_浸水ランク int, Case2水門開放津波浸水想定_浸水深 float, Case2水門閉鎖津波浸水想定_説明 string, Case2水門閉鎖津波浸水想定_浸水ランク int, Case2水門閉鎖津波浸水想定_浸水深 float, 土砂災害警戒区域_区域区分 int, 土砂災害警戒区域_現象区分 int, LOD2 int,
      LOD int, gml_id string
tileset (writer CESIUM3DTILES_1)
    attributes: 計測高さ float, 図形面積 float, 建物地上階数 int, 建物地下階数 int, 建物構造 string, 建物用途 string, 延べ面積換算係数 float, 住所 string, 用途地域 string, 高度地区 string, 防火及び準防火地域 string, 地区計画 string, 荒川洪水浸水想定_計画規模_浸水ランク int, 荒川洪水浸水想定_計画規模_浸水深 float, 荒川洪水浸水想定_計画規模_継続時間 float, 荒川洪水浸水想定_想定最大規模_浸水ランク int, 荒川洪水浸水想定_想定最大規模_浸水深 float, 荒川洪水浸水想定_想定最大規模_継続時間 float, 江戸川洪水浸水想定_計画規模_浸水ランク int, 江戸川洪水浸水想定_計画規模_浸水深 float, 江戸川洪水浸水想定_計画規模_継続時間 float, 江戸川洪水浸水想定_想定最大規模_浸水ランク int, 江戸川洪水浸水想定_想定最大規模_浸水深 float, 江戸川洪水浸水想定_想定最大規模_継続時間 float, 利根川洪水浸水想定_計画規模_浸水ランク int, 利根川洪水浸水想定_計画規模_浸水深 float, 利根川洪水浸水想定_計画規模_継続時間 float, 利根川洪水浸水想定_想定最大規模_浸水ランク int, 利根川洪水浸水想定_想定最大規模_浸水深 float, 利根川洪水浸水想定_想定最大規模_継続時間 float,
      多摩川洪水浸水想定_計画規模_浸水ランク int, 多摩川洪水浸水想定_計画規模_浸水深 float, 多摩川洪水浸水想定_計画規模_継続時間 float, 多摩川洪水浸水想定_想定最大規模_浸水ランク int, 多摩川洪水浸水想定_想定最大規模_浸水深 float, 多摩川洪水浸水想定_想定最大規模_継続時間 float, 神田川洪水浸水想定_想定最大規模_浸水ランク int, 神田川洪水浸水想定_想定最大規模_浸水深 float, 神田川洪水浸水想定_想定最大規模_継続時間 float, 石神井川及び白子川流域洪水浸水想定_想定最大規模_浸水ランク int, 石神井川及び白子川流域洪水浸水想定_想定最大規模_浸水深 float, 石神井川及び白子川流域洪水浸水想定_想定最大規模_継続時間 float, 江東内部河川流域洪水浸水想定_想定最大規模_浸水ランク int, 江東内部河川流域洪水浸水想定_想定最大規模_浸水深 float, 江東内部河川流域洪水浸水想定_想定最大規模_継続時間 float, 城南地区河川流域洪水浸水想定_想定最大規模_浸水ランク int, 城南地区河川流域洪水浸水想定_想定最大規模_浸水深 float, 城南地区河川流域洪水浸水想定_想定最大規模_継続時間 float, 野川、仙川、入間川、谷沢川及び丸子川流域洪水浸水想定_想定最大規模_浸水ランク int, 野川、仙川、入間川、谷沢川及び丸子川流域洪水浸水想定_想定最大規模_浸水深 float, 野川、仙川、入間川、谷沢川及び丸子川流域洪水浸水想定_想定最大規模_継続時間 float, Case2水門開放津波浸水想定_説明 string, Case2水門開放津波浸水想定_浸水ランク int, Case2水門開放津波浸水想定_浸水深 float, Case2水門閉鎖津波浸水想定_説明 string, Case2水門閉鎖津波浸水想定_浸水ランク int, Case2水門閉鎖津波浸水想定_浸水深 float, 土砂災害警戒区域_区域区分 int, 土砂災害警戒区域_現象区分 int, LOD2 int,
      LOD int, gml_id string
attributes (writer CSV2_3)
    attributes: 計測高さ string, 図形面積 string, 建物地上階数 string, 建物地下階数 string, 建物構造 string, 建物用途 string, 延べ面積換算係数 string, 住所 string, 用途地域 string, 高度地区 string, 防火及び準防火地域 string, 地区計画 string, 荒川洪水浸水想定_計画規模_浸水ランク string, 荒川洪水浸水想定_計画規模_浸水深 string, 荒川洪水浸水想定_計画規模_継続時間 string, 荒川洪水浸水想定_想定最大規模_浸水ランク string, 荒川洪水浸水想定_想定最大規模_浸水深 string, 荒川洪水浸水想定_想定最大規模_継続時間 string, 江戸川洪水浸水想定_計画規模_浸水ランク string, 江戸川洪水浸水想定_計画規模_浸水深 string, 江戸川洪水浸水想定_計画規模_継続時間 string, 江戸川洪水浸水想定_想定最大規模_浸水ランク string, 江戸川洪水浸水想定_想定最大規模_浸水深 string, 江戸川洪水浸水想定_想定最大規模_継続時間 string, 利根川洪水浸水想定_計画規模_浸水ランク string, 利根川洪水浸水想定_計画規模_浸水深 string, 利根川洪水浸水想定_計画規模_継続時間 string, 利根川洪水浸水想定_想定最大規模_浸水ランク string, 利根川洪水浸水想定_想定最大規模_浸水深 string, 利根川洪水浸水想定_想定最大規模_継続時間 string,
      多摩川洪水浸水想定_計画規模_浸水ランク string, 多摩川洪水浸水想定_計画規模_浸水深 string, 多摩川洪水浸水想定_計画規模_継続時間 string, 多摩川洪水浸水想定_想定最大規模_浸水ランク string, 多摩川洪水浸水想定_想定最大規模_浸水深 string, 多摩川洪水浸水想定_想定最大規模_継続時間 string, 神田川洪水浸水想定_想定最大規模_浸水ランク string, 神田川洪水浸水想定_想定最大規模_浸水深 string, 神田川洪水浸水想定_想定最大規模_継続時間 string, 石神井川及び白子川流域洪水浸水想定_想定最大規模_浸水ランク string, 石神井川及び白子川流域洪水浸水想定_想定最大規模_浸水深 string, 石神井川及び白子川流域洪水浸水想定_想定最大規模_継続時間 string, 江東内部河川流域洪水浸水想定_想定最大規模_浸水ランク string, 江東内部河川流域洪水浸水想定_想定最大規模_浸水深 string, 江東内部河川流域洪水浸水想定_想定最大規模_継続時間 string, 城南地区河川流域洪水浸水想定_想定最大規模_浸水ランク string, 城南地区河川流域洪水浸水想定_想定最大規模_浸水深 string, 城南地区河川流域洪水浸水想定_想定最大規模_継続時間 string, 野川、仙川、入間川、谷沢川及び丸子川流域洪水浸水想定_想定最大規模_浸水ランク string, 野川、仙川、入間川、谷沢川及び丸子川流域洪水浸水想定_想定最大規模_浸水深 string, 野川、仙川、入間川、谷沢川及び丸子川流域洪水浸水想定_想定最大規模_継続時間 string, Case2水門開放津波浸水想定_説明 string, Case2水門開放津波浸水想定_浸水ランク string, Case2水門開放津波浸水想定_浸水深 string, Case2水門閉鎖津波浸水想定_説明 string, Case2水門閉鎖津波浸水想定_浸水ランク string, Case2水門閉鎖津波浸水想定_浸水深 string, 土砂災害警戒区域_区域区分 string, 土砂災害警戒区域_現象区分 string, LOD2 string,
      LOD string, gml_id string

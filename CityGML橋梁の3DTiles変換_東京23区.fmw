FME workspace CityGML橋梁の3DTiles変換_東京23区.fmw

Parameters:
- CITYGML_BRID_FOLDER = C:\Users\takas\PSS Dropbox\All_Project\20200001_mri_digitaltwin\05_citygml\東京23区+八王子（南大沢）\20210129_国際航業納品\13201_八王子市\citygml\13201\udx\brid   # CityGML橋梁データフォルダー（brid）
- DestDataset_CESIUM3DTILES = $(FME_MF_DIR)20210213_橋梁変換結果\13201_hachioji   # 3DTiles出力先ルートフォルダー
- SourceDataset_CITYGML = $(CITYGML_BRID_FOLDER)/*.gml   # CityGML橋梁データフォルダー (brid)

Readers:
- CITYGML_1: CITYGML from $(SourceDataset_CITYGML)

Writers:
- CESIUM3DTILES_1: CESIUM3DTILES to $(DestDataset_CESIUM3DTILES)

CityModel (reader CITYGML_1)
    attributes: citygml_target_uri xml_buffer, gml_description xml_buffer, gml_name xml_buffer, citygml_city_object_member{}.xlink_href xml_buffer, citygml_appearance_member{}.xlink_href xml_buffer, gml_feature_member{}.xlink_href xml_buffer
Bridge (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_year_of_construction xml_buffer, citygml_year_of_demolition xml_buffer, citygml_is_movable xml_boolean, citygml_outer_bridge_construction{}.xlink_href xml_buffer, citygml_outer_bridge_installation{}.xlink_href xml_buffer, citygml_interior_bridge_installation{}.xlink_href xml_buffer, citygml_bounded_by{}.xlink_href xml_buffer, citygml_level_of_detail{} xml_buffer, citygml_interior_bridge_room{}.xlink_href xml_buffer,
      citygml_consists_of_bridge_part{}.xlink_href xml_buffer, citygml_address{}.xlink_href xml_buffer
    -> CsmapReprojector
CsmapReprojector
    DEST = EPSG:4326
    GEOID_HEIGHT_GRID = $(FME_HOME)Reproject\GeoidHeightGrids\World\Egm96-Wgs84.gdc
    INTERPOLATION_TYPE_NAME = Nearest Neighbor
    RASTER_CELL_SIZE = Preserve Cells
    RASTER_TOLERANCE = 0.0
    VERTICAL_HANDLING = Orthometric height -> Geocentric or ellipsoid height
    REPROJECTED -> brid (writer CESIUM3DTILES_1)
brid (writer CESIUM3DTILES_1)
